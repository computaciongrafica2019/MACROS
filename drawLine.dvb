Attribute VB_Name = "Module1"
Sub createLine()
    Dim acadApp As AcadApplication
    Set acadApp = New AcadApplication
    acadApp.Visible = True
    acadApp.Documents.Add
    
    Dim ObjLinea As AcadLine
    
    Dim PuntoInicial(1 To 3) As Double
    Dim PuntoFinal(1 To 3) As Double
    
    PuntoInicial(1) = 100: PuntoInicial(2) = 100: PuntoInicial(3) = 0
    PuntoFinal(1) = 200: PuntoFinal(2) = 200: PuntoFinal(3) = 0
    
    Set ObjLinea = acadApp.ActiveDocument.ModelSpace.AddLine(PuntoInicial, PuntoFinal)
End Sub
