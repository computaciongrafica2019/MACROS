Attribute VB_Name = "Module1"
Sub Macro1()
    Dim Pi As Double
    Pi = 3.141516

    Dim linea As AcadLine
    Dim circulo As AcadCircle
    
    Dim pto1(1 To 3) As Double
    Dim pto2(1 To 3) As Double
    Dim pto3(1 To 3) As Double
    Dim pto4(1 To 3) As Double
    Dim ref1(1 To 3) As Double
    Dim ref2(1 To 3) As Double
    
    pto1(1) = 0: pto1(2) = 0: pto1(3) = 0
    pto2(1) = 100: pto2(2) = 100: pto2(3) = 0
    pto3(1) = 125: pto3(2) = 125: pto3(3) = 0
    pto4(1) = 50: pto4(2) = 50: pto4(3) = 0
    ref1(1) = 7: ref1(2) = 37.6: ref1(3) = 0
    ref2(1) = 38.6: ref2(2) = 6: ref2(3) = 0
    
    Set linea = AcadApplication.ActiveDocument.ModelSpace.AddLine(pto1, pto2)
    linea.color = 70
    
    Set circulo = AcadApplication.ActiveDocument.ModelSpace.AddCircle(pto2, 25)
    circulo.color = 40
    Set circulo = AcadApplication.ActiveDocument.ModelSpace.AddCircle(pto2, 20)
    circulo.color = 40
    Set circulo = AcadApplication.ActiveDocument.ModelSpace.AddCircle(pto2, 15)
    circulo.color = 40
    Set circulo = AcadApplication.ActiveDocument.ModelSpace.AddCircle(pto2, 10)
    circulo.color = 40
    Set circulo = AcadApplication.ActiveDocument.ModelSpace.AddCircle(pto2, 5)
    circulo.color = 30
    
    Set circulo = AcadApplication.ActiveDocument.ModelSpace.AddCircle(pto2, 35)
    circulo.color = 50
    Set circulo = AcadApplication.ActiveDocument.ModelSpace.AddCircle(pto2, 30)
    circulo.color = 50
    
    Set circulo = AcadApplication.ActiveDocument.ModelSpace.AddCircle(pto3, 15)
    circulo.color = 212
    arreglo = circulo.ArrayPolar(10, 2 * Pi, pto2)
    Set circulo = AcadApplication.ActiveDocument.ModelSpace.AddCircle(pto3, 10)
    circulo.color = 212
    arreglo = circulo.ArrayPolar(10, 2 * Pi, pto2)
    Set circulo = AcadApplication.ActiveDocument.ModelSpace.AddCircle(pto3, 5)
    circulo.color = 212
    arreglo = circulo.ArrayPolar(10, 2 * Pi, pto2)
    
    Set circulo = AcadApplication.ActiveDocument.ModelSpace.AddCircle(pto4, 5)
    circulo.color = 70
    arreglo = circulo.ArrayPolar(20, Pi / 8, ref1)
    arreglo = circulo.ArrayPolar(20, -Pi / 8, ref2)
        
End Sub

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
Private Sub AcadDocument_BeginSave(ByVal FileName As String)

End Sub
