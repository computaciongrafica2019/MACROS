Attribute VB_Name = "MacroACAD1"
Sub MacroAutoCAD()

'msm = "Hola Mundo"
'ThisDrawing.Utility.Prompt (msm)
Dim Pi As Double
Pi = 3.141516

Dim ObjCirculo As AcadCircle
Dim ObjCirculo2 As AcadCircle

Dim Centro(1 To 3) As Double
        Centro(1) = 30: Centro(2) = 30: Centro(3) = 0

Dim Centro2(1 To 3) As Double
        Centro2(1) = 50: Centro2(2) = 30: Centro2(3) = 0
        
Dim Borde(1 To 3) As Double
        Borde(1) = 40: Borde(2) = 30: Borde(3) = 0
        
Dim Radio As Double
        Radio = 10

Set ObjCirculo = AcadApplication.ActiveDocument.ModelSpace.AddCircle(Centro, Radio)
Set ObjCirculo2 = AcadApplication.ActiveDocument.ModelSpace.AddCircle(Centro2, Radio)


ObjCirculo.color = 3
VarMatriz = ObjCirculo.ArrayPolar(25, Pi / 2, Borde)

ObjCirculo.color = 2
VarMatriz = ObjCirculo.ArrayPolar(25, -Pi / 2, Borde)

ObjCirculo2.color = 1
VarMatriz = ObjCirculo2.ArrayPolar(25, -Pi / 2, Borde)

ObjCirculo2.color = 0
VarMatriz = ObjCirculo2.ArrayPolar(25, Pi / 2, Borde)


End Sub
